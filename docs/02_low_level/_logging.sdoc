[DOCUMENT]
TITLE: Logging
REQ_PREFIX: ZEP-

[GRAMMAR]
ELEMENTS:
- TAG: REQUIREMENT
  FIELDS:
  - TITLE: UID
    TYPE: String
    REQUIRED: False
  - TITLE: STATUS
    TYPE: String
    REQUIRED: False
  - TITLE: TYPE
    TYPE: String
    REQUIRED: False
  - TITLE: COMPONENT
    TYPE: String
    REQUIRED: False
  - TITLE: TITLE
    TYPE: String
    REQUIRED: False
  - TITLE: STATEMENT
    TYPE: String
    REQUIRED: False
  - TITLE: USER_STORY
    TYPE: String
    REQUIRED: False
  - TITLE: DISCUSSION_DATE
    TYPE: String
    REQUIRED: False
  - TITLE: REVIEW_COMMENT
    TYPE: String
    REQUIRED: False
  RELATIONS:
  - TYPE: Parent

[REQUIREMENT]
UID: ZEP-63
STATUS: Draft
TYPE: Functional
COMPONENT: Logging
TITLE: Dedicated Logging Thread Support
STATEMENT: >>>
Zephyr shall support isolation of logging from other functionality.
<<<
USER_STORY: >>>
As a Zephyr OS user I want to be able to configure logging of events so the execution of logging activities does have no or only a minimal impact to the timing behaviour of my application.
<<<
DISCUSSION_DATE: >>>
2022/4/13 - ok - pf
<<<

[REQUIREMENT]
UID: ZEP-64
STATUS: Draft
TYPE: Functional
COMPONENT: Logging
TITLE: Logs available for post processing
STATEMENT: >>>
Zephyr logging shall produce logs that are capable of being post processed.
<<<
USER_STORY: >>>
As a Zephyr OS user I want the logging information to be stored in a format which allows to be read possibly converted or displayed by COTS tools.
<<<
DISCUSSION_DATE: >>>
2022/4/13 - ok - pf
<<<

[REQUIREMENT]
UID: ZEP-65
STATUS: Draft
TYPE: Functional
COMPONENT: Logging
TITLE: Formatting log messages
STATEMENT: >>>
Zephyr logging shall support formatting of log messages to enable filtering.
<<<
USER_STORY: >>>
As a Zephyr OS user I want to be able my application to format texts (printf alike) into the log message.
<<<
DISCUSSION_DATE: >>>
2022/10/25 - Incomplete - Need more information.  Specify format at this point.
<<<
REVIEW_COMMENT: >>>
Question: formatting in which way? length, color, tags, etc?
<<<

[REQUIREMENT]
UID: ZEP-66
STATUS: Draft
TYPE: Functional
COMPONENT: Logging
TITLE: Logging Filtering Support
STATEMENT: >>>
Zephyr logging system shall support filtering based on severity level.
<<<
USER_STORY: >>>
As a Zephyr OS user I want to be able to distinguish between different severity level for my log messages (e.g. DEBUG, INFO, WARN, ERROR, PANIC).
<<<
DISCUSSION_DATE: >>>
2022/10/25 -ok
<<<
REVIEW_COMMENT: >>>
Question: Filtering during runtime or a kconfig option to initially set the filter for logging
<<<

[REQUIREMENT]
UID: ZEP-67
STATUS: Draft
TYPE: Functional
COMPONENT: Logging
TITLE: Multiple Backend Logging Support
STATEMENT: >>>
Zephyr shall support logging messages to multiple system resources.
<<<
USER_STORY: >>>
As a Zephyr OS user I want to be able to simultaneously log to different channels which may store / redirect the information on / to different hardware (EEPROM, Flash, FRAM, UART, Ethernet, USB etc.).
<<<
DISCUSSION_DATE: >>>
2022/10/25 -ok
<<<
REVIEW_COMMENT: >>>
Question: What kind of backends shall be supported? More than one at a time?   Word choices.... backends/devices/channels/destinations/resources (devices, memory, ....) )
<<<

[REQUIREMENT]
UID: ZEP-68
STATUS: Draft
TYPE: Functional
COMPONENT: Logging
TITLE: Deferred Logging Support
STATEMENT: >>>
Zephyr shall support deferred logging (TODO: need more detail about the constraints and limits on what can be deferred).
<<<
USER_STORY: >>>
As a Zephyr OS user I want a minimal influence of logging activities to the timing behaviour of my application. Time consuming logging tasks shall be done in the background.
<<<
DISCUSSION_DATE: >>>
2022/10/25 -ok
<<<
