[DOCUMENT]
TITLE: C library
REQ_PREFIX: ZEP-

[GRAMMAR]
ELEMENTS:
- TAG: REQUIREMENT
  FIELDS:
  - TITLE: UID
    TYPE: String
    REQUIRED: False
  - TITLE: STATUS
    TYPE: String
    REQUIRED: False
  - TITLE: TYPE
    TYPE: String
    REQUIRED: False
  - TITLE: COMPONENT
    TYPE: String
    REQUIRED: False
  - TITLE: TITLE
    TYPE: String
    REQUIRED: False
  - TITLE: STATEMENT
    TYPE: String
    REQUIRED: False
  - TITLE: USER_STORY
    TYPE: String
    REQUIRED: False
  - TITLE: DISCUSSION_DATE
    TYPE: String
    REQUIRED: False
  - TITLE: REVIEW_COMMENT
    TYPE: String
    REQUIRED: False
  RELATIONS:
  - TYPE: Parent

[REQUIREMENT]
UID: ZEP-12
STATUS: Draft
TYPE: Functional
COMPONENT: C Library
TITLE: Formatted output
STATEMENT: >>>
Zephyr shall support formatted output.
<<<
USER_STORY: >>>
As a Zephyr OS user, I want to be able to printf with various output formats.
<<<
DISCUSSION_DATE: >>>
20221122.0
<<<
RELATIONS:
- TYPE: Parent
  VALUE: ZEP-2

[REQUIREMENT]
UID: ZEP-13
STATUS: Draft
TYPE: Functional
COMPONENT: C Library
TITLE: Floating Point Math Support
STATEMENT: >>>
Zephyr shall support floating point math libraries for processors where floating point is available.
<<<
USER_STORY: >>>
As a Zephyr OS user, I want to be able to calculate with floating point numbers.
<<<
DISCUSSION_DATE: >>>
20221122.0
<<<
RELATIONS:
- TYPE: Parent
  VALUE: ZEP-2

[REQUIREMENT]
UID: ZEP-14
STATUS: Draft
TYPE: Functional
COMPONENT: C Library
TITLE: Boolean Primitives Support
STATEMENT: >>>
Zephyr shall support boolean primitives.
<<<
USER_STORY: >>>
As a Zephyr OS user, I want to be able to work with boolean values and logic.
<<<
DISCUSSION_DATE: >>>
20221122.0
<<<
RELATIONS:
- TYPE: Parent
  VALUE: ZEP-2

[REQUIREMENT]
UID: ZEP-15
STATUS: Draft
TYPE: Functional
COMPONENT: C Library
TITLE: Standard Unix time interface
STATEMENT: >>>
Zephyr shall support the standard unix time interface.
<<<
USER_STORY: >>>
As a Zephyr User, I want to be able to use system time.
<<<
DISCUSSION_DATE: >>>
20221122.0
<<<
RELATIONS:
- TYPE: Parent
  VALUE: ZEP-2

[REQUIREMENT]
UID: ZEP-16
STATUS: Draft
TYPE: Functional
COMPONENT: C Library
TITLE: Strings support
STATEMENT: >>>
Zephyr shall support an interface to manage strings.
<<<
USER_STORY: >>>
As a Zephyr OS user, I want to be able to manipulate text strings.
<<<
DISCUSSION_DATE: >>>
20221122.0
<<<
RELATIONS:
- TYPE: Parent
  VALUE: ZEP-2

[REQUIREMENT]
UID: ZEP-17
STATUS: Draft
TYPE: Functional
COMPONENT: C Library
TITLE: Moving/copying regions of memory
STATEMENT: >>>
Zephyr shall support an interface to move contents between regions of memory.
<<<
USER_STORY: >>>
As a Zephyr OS user, I want to copy the memory contents to different addresses.
<<<
DISCUSSION_DATE: >>>
20221122.0
<<<
RELATIONS:
- TYPE: Parent
  VALUE: ZEP-2

[REQUIREMENT]
UID: ZEP-18
STATUS: Draft
TYPE: Functional
COMPONENT: C Library
TITLE: I/O based interface
STATEMENT: >>>
Zephyr shall support a file i/O based interface for driver communication.
<<<
USER_STORY: >>>
As a Zephyr OS user, I want to be able to use File I/O functions.
<<<
DISCUSSION_DATE: >>>
20221122.0
<<<
REVIEW_COMMENT: >>>
A wrong C header seems to be included: stdint.h does not have to do with I/O.
<<<
RELATIONS:
- TYPE: Parent
  VALUE: ZEP-2

[REQUIREMENT]
UID: ZEP-19
STATUS: Draft
TYPE: Functional
COMPONENT: C Library
TITLE: C99 integer types
STATEMENT: >>>
Zephyr shall support standard C99 integer types.
<<<
USER_STORY: >>>
As a Zephyr OS user, I want to be able to calculate with C99 Integers.
<<<
DISCUSSION_DATE: >>>
20221122.0
<<<
RELATIONS:
- TYPE: Parent
  VALUE: ZEP-2

[REQUIREMENT]
UID: ZEP-20
STATUS: Draft
TYPE: Functional
COMPONENT: C Library
TITLE: Standard System Error Numbers (IEEE Std 1003.1-2017)
STATEMENT: >>>
Zephyr shall support standard system error numbers as defined by IEEE Std 1003.1-2017.
<<<
USER_STORY: >>>
As a Zephyr OS user, I want to be able to use IEE Std 1003.1-2017 Error Numbers for Interoperability.
<<<
DISCUSSION_DATE: >>>
20221129.0
<<<
RELATIONS:
- TYPE: Parent
  VALUE: ZEP-2

[REQUIREMENT]
UID: ZEP-21
STATUS: Draft
TYPE: Functional
COMPONENT: C Library
TITLE: Document set of Zephyr OS required C librariy functions in Safety Manual
STATEMENT: >>>
The set of C Library functions required by Zephyr needs to be documented in the Zephyr Safety Manual.
<<<
USER_STORY: >>>
As a Zephyr user, I want to know which C library functions are being called by the Zephyr OS safety scope code.
<<<
DISCUSSION_DATE: >>>
TBD: Revisit after subset defined.
<<<
RELATIONS:
- TYPE: Parent
  VALUE: ZEP-2

[REQUIREMENT]
UID: ZEP-22
STATUS: Draft
TYPE: Functional
COMPONENT: C Library
TITLE: Support external C libraries documentation in Zephyr Safety Manual
STATEMENT: >>>
The Zephyr Safety Manual needs to specify how to configure the support of external C Libraries.
<<<
USER_STORY: >>>
As a Zephyr User, I need to understand how to configure the external C libraries to align with the validation that has been performed.
<<<
DISCUSSION_DATE: >>>
TBD: Revisit after subset defined.
<<<
RELATIONS:
- TYPE: Parent
  VALUE: ZEP-2
