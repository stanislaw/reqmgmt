[DOCUMENT]
TITLE: Zephyr Functional Requirements
REQ_PREFIX: ZEP-

[GRAMMAR]
ELEMENTS:
- TAG: REQUIREMENT
  FIELDS:
  - TITLE: UID
    TYPE: String
    REQUIRED: False
  - TITLE: STATUS
    TYPE: String
    REQUIRED: False
  - TITLE: TYPE
    TYPE: String
    REQUIRED: False
  - TITLE: COMPONENT
    TYPE: String
    REQUIRED: False
  - TITLE: TITLE
    TYPE: String
    REQUIRED: False
  - TITLE: STATEMENT
    TYPE: String
    REQUIRED: False
  - TITLE: USER_STORY
    TYPE: String
    REQUIRED: False
  - TITLE: DISCUSSION_DATE
    TYPE: String
    REQUIRED: False
  - TITLE: REVIEW_COMMENT
    TYPE: String
    REQUIRED: False
  RELATIONS:
  - TYPE: Parent

[SECTION]
TITLE: Hardware Architecture Interface

[REQUIREMENT]
UID: ZEP-8
STATUS: Draft
TYPE: Functional
COMPONENT: Hardware Architecture Interface
TITLE: Atomic Operations
STATEMENT: >>>
Zephyr shall provide an interface functionality to access memory while ensuring mutual exclusion. Note: Implementation by atomic variables and accessing them by APIs.
<<<
USER_STORY: >>>
As a Zephyr OS user I want to read from or write into a memory areas without being disturbed by other threads or ISRs.
<<<
DISCUSSION_DATE: >>>
2022/3/30 - ok - pq
<<<
RELATIONS:
- TYPE: Parent
  VALUE: ZEP-1

[REQUIREMENT]
UID: ZEP-9
STATUS: Draft
TYPE: Functional
COMPONENT: Hardware Architecture Interface
TITLE: Thread Context Switching
STATEMENT: >>>
Zephyr shall provide a mechanism for context switching between threads.
<<<
USER_STORY: >>>
As a Zephyr OS user I want to execute code concurrently in one or more threads and when interrupted at a code location in a thread, to continue at the very same location.
<<<
DISCUSSION_DATE: >>>
2022/3/30 - ok - pf
<<<
RELATIONS:
- TYPE: Parent
  VALUE: ZEP-1

[REQUIREMENT]
UID: ZEP-10
STATUS: Draft
TYPE: Functional
COMPONENT: Hardware Architecture Interface
TITLE: Software Exceptions
STATEMENT: >>>
Zephyr shall provide an interface to implement software exceptions.
<<<
USER_STORY: >>>
As a Zephyr OS user I want to catch any software exception and handle it according to my application needs.
<<<
DISCUSSION_DATE: >>>
2022/3/30 - ok - pq
<<<
RELATIONS:
- TYPE: Parent
  VALUE: ZEP-1

[REQUIREMENT]
UID: ZEP-11
STATUS: Draft
TYPE: Functional
COMPONENT: Hardware Architecture Interface
TITLE: Processor Mode Support
STATEMENT: >>>
Zephyr shall provide an interface for managing processor modes.
<<<
USER_STORY: >>>
If MCU power state was meant here:
As a Zephyr OS user I want to control the MCU's power saving mode such e.g. operation, sleep, deep sleep or similar as supported by the selected MCU.
<<<
DISCUSSION_DATE: >>>
2022/7/21 - ok - pf
<<<
REVIEW_COMMENT: >>>
What is lifecycle - power on, standby, power off?  or ???? 

Clarification: Starting and Stopping, and putting it into Stand-By Mode (whatever the processor supports)
<<<
RELATIONS:
- TYPE: Parent
  VALUE: ZEP-1

[/SECTION]

[SECTION]
TITLE: Device Driver API

[REQUIREMENT]
UID: ZEP-45
STATUS: Draft
TYPE: Functional
COMPONENT: Device Driver API
TITLE: Device Driver Abstraction
STATEMENT: >>>
Zephyr shall provide abstraction of device drivers with common functionalities as an intermediate interface between applications and device drivers, where such interface is implemented by individual device drivers.

Proposal for replacement: Zephyr shall provide an interface between application and individual device drivers to provide an abstraction of device drivers with common functionalities.
<<<
USER_STORY: >>>
=N21 & "

Remark: What is the difference to ZEP006?"
<<<
DISCUSSION_DATE: >>>
Needs clarification - what are common functionalities?   Link to description?
<<<
REVIEW_COMMENT: >>>
What are common functionalities?

Clarification: Abstract API drivers, UART. Set of files asociated with that. Include drivers. 50+ files. Best place to look at is the documentation (not the files).
<<<

[REQUIREMENT]
UID: ZEP-46
STATUS: Draft
TYPE: Functional
COMPONENT: Device Driver API
TITLE: Expose kernel to hardware interrupts
STATEMENT: >>>
Zephyr shall provide an interface for managing a defined set of hardware exceptions (including interupts) across all systems.
<<<
USER_STORY: >>>
As a Zephyr OS user I want hardware exeptions (hardware failures, programming mistakes) to be handled gracefully (no program crashes as far as possible).
<<<
DISCUSSION_DATE: >>>
2022/4/13 - ok - pf
<<<
REVIEW_COMMENT: >>>
What does "system" mean in this context? Architecture?

NP: Now I think system means HW platform.
<<<

[/SECTION]

[SECTION]
TITLE: Exception and Error Handling

[REQUIREMENT]
UID: ZEP-47
STATUS: Draft
TYPE: Functional
COMPONENT: Exception and Error Handling
TITLE: Fatal Exception Error Handler
STATEMENT: >>>
Zephyr shall provide default handlers for exceptions.
<<<
USER_STORY: >>>
As a Zephyr OS user I want execptions which I did not handle explicitely (by mistake or on purpose) to be caught by a default handler, defined either by Zephyr OS or by myself.
<<<
DISCUSSION_DATE: >>>
2022/4/13 - ok -pq - need definition of exceptions vs fatal errors
<<<

[REQUIREMENT]
UID: ZEP-48
STATUS: Draft
TYPE: Functional
COMPONENT: Exception and Error Handling
TITLE: Default handler for fatal errors
STATEMENT: >>>
Zephyr shall provide default handlers for fatal errors that do not have a dedicated handler.
<<<
USER_STORY: >>>
TBD: =N25
<<<
DISCUSSION_DATE: >>>
2022/4/13 - ok - pq
<<<

[REQUIREMENT]
UID: ZEP-49
STATUS: Draft
TYPE: Functional
COMPONENT: Exception and Error Handling
TITLE: Assigning a specific handler
STATEMENT: >>>
Zephyr shall provide an interface to assign a specific handler with an exception.
<<<

[REQUIREMENT]
UID: ZEP-50
STATUS: Draft
TYPE: Functional
COMPONENT: Exception and Error Handling
TITLE: Assigning a specific handler (2)
STATEMENT: >>>
Zephyr shall provide an interface to assign a specific handler for a fatal error.
<<<

[/SECTION]

[SECTION]
TITLE: Interrupts

[REQUIREMENT]
UID: ZEP-58
STATUS: Draft
TYPE: Functional
COMPONENT: Interrupts
TITLE: Service routine for handling interrupts (ISR)
STATEMENT: >>>
Zephyr shall provide support a service routine for handling interrupts (ISR).
<<<
USER_STORY: >>>
TBD: Duplicate to line 30? delete?
<<<
DISCUSSION_DATE: >>>
2022/4/13 - ok - pq
<<<

[REQUIREMENT]
UID: ZEP-59
STATUS: Draft
TYPE: Functional
COMPONENT: Interrupts
TITLE: Multi-level interrupts
STATEMENT: >>>
Zephyr shall support multi-level preemptive interrupt priorities, when supported by hardware. Note: detailed analysis to demonstrate non interferenace will be needed here.
<<<
USER_STORY: >>>
TBD
<<<
DISCUSSION_DATE: >>>
2022/4/13 - ok - pf
<<<

[REQUIREMENT]
UID: ZEP-60
STATUS: Draft
TYPE: Functional
COMPONENT: Interrupts
TITLE: Associating application code with interrupts
STATEMENT: >>>
Zephyr shall provide an interface for associating application code with specific interrupts. (CLARIFY: Can it be a deferred procedure call at interrupt context? Would be different requirement)
<<<
USER_STORY: >>>
TBD
<<<
DISCUSSION_DATE: >>>
2022/4/13 - ok - pf
<<<

[REQUIREMENT]
UID: ZEP-61
STATUS: Draft
TYPE: Functional
COMPONENT: Interrupts
TITLE: Enabling interrupts
STATEMENT: >>>
Zephyr shall provide mechanisms to enable interrupts.
<<<
USER_STORY: >>>
As a Zephyr OS user I want to be able to enable each individual and a global interrupt according to my applications needs during program execution.
<<<
DISCUSSION_DATE: >>>
2022/8/29 - ok -pf
<<<

[REQUIREMENT]
UID: ZEP-62
STATUS: Draft
TYPE: Functional
COMPONENT: Interrupts
TITLE: Disabling interrupts
STATEMENT: >>>
Zephyr shall provide mechanisms to disable interrupts.
<<<
USER_STORY: >>>
As a Zephyr OS user I want to be able to disable each individual and a global interrupt according to my applications needs during program execution.
<<<
DISCUSSION_DATE: >>>
2022/8/29 - ok -pf
<<<

[/SECTION]

[SECTION]
TITLE: Memory protection

[REQUIREMENT]
UID: ZEP-69
STATUS: Draft
TYPE: Functional
COMPONENT: Memory Protection
TITLE: Memory Protection
STATEMENT: >>>
Zephyr shall support memory protection features to isolate a thread's memory region.
<<<
USER_STORY: >>>
As a Zephyr OS user I want memory to be allocated and protected to my application threads preventing mistakenly access to foreign memory as far as the hardware allows.
<<<
DISCUSSION_DATE: >>>
2022/10/25 - ok
<<<
REVIEW_COMMENT: >>>
Functional it is memory management, but it also strongly relates to the architecture abstraction and memory access
<<<

[REQUIREMENT]
UID: ZEP-70
STATUS: Draft
TYPE: Functional
COMPONENT: Memory Protection
TITLE: Granting access to kernel objects
STATEMENT: >>>
Zephyr shall provide a mechanism to grant user threads access to kernel objects.
<<<
USER_STORY: >>>
As a Zephyr OS user I want, from the user space, under certain condidtions, access to kernel objects.
<<<
DISCUSSION_DATE: >>>
2022/10/25 - ok
<<<
REVIEW_COMMENT: >>>
What are the conditions to a user thread to get access to a kernel object?
<<<

[REQUIREMENT]
UID: ZEP-71
STATUS: Draft
TYPE: Functional
COMPONENT: Memory Protection
TITLE: Separation between user and kernel threads for memory access
STATEMENT: >>>
Zephyr shall be able to differentiate between user threads and kernel threads for memory access.
<<<
USER_STORY: >>>
As a Zephyr OS user I want, from the kernel space, unconditoned access to kernel objects.
<<<
DISCUSSION_DATE: >>>
2022/10/25 - ok
<<<

[REQUIREMENT]
UID: ZEP-72
STATUS: Draft
TYPE: Functional
COMPONENT: Memory Protection
TITLE: Safely handle unimplemented calls or invalid system calls
STATEMENT: >>>
Zephyr shall have a defined behaviour when an invocation of an unimplemented system call is made.
<<<
USER_STORY: >>>
As a Zephyr OS user I want Zephyr OS to indicate any unimplemented system call by an appropriate error message.
<<<
DISCUSSION_DATE: >>>
2022/4/13 - ok - pq
<<<
REVIEW_COMMENT: >>>
What is an "unimplemented system call"? An empty system call function? Can I call something that is not there it all? Isn't this more a topic for security? - makes sense to handle this from the safety perspective, but still raises some quesitions here.
<<<

[REQUIREMENT]
UID: ZEP-73
STATUS: Draft
TYPE: Functional
COMPONENT: Memory Protection
TITLE: Response to invalid system call IDs
STATEMENT: >>>
Zephyr shall have a defined behavior when an invalid system call ID is used.
<<<
USER_STORY: >>>
As a Zephyr OS user I want Zephyr OS to indicate invalid system call by an appropriate error message.
<<<
DISCUSSION_DATE: >>>
2022/4/13 - ok - pq
<<<

[REQUIREMENT]
UID: ZEP-74
STATUS: Draft
TYPE: Functional
COMPONENT: Memory Protection
TITLE: Prevent user threads creating higher priority threasds
STATEMENT: >>>
Zephyr shall prevent user threads from creating new threads that are higher priority than the caller.
<<<
USER_STORY: >>>
As a Zephyr OS user I want ... ???

(Sorry I still do not see the reason for such a requirement, if I, as a user, do not want to get swapped out of my thread creating thread, I can take care of that myself. If there are security (safety?) thought behind, it would be nice to understand them and document them here.)
<<<
DISCUSSION_DATE: >>>
2022/4/26 -ok - pq
<<<

[REQUIREMENT]
UID: ZEP-75
STATUS: Draft
TYPE: Functional
COMPONENT: Memory Protection
TITLE: Revoking threads permissions on a kernel object
STATEMENT: >>>
Zephyr shall support revoking permission to a kernel object. User mode threads may only revoke their own access to an object.
<<<
USER_STORY: >>>
As a Zephyr OS user I want to be protected against other user threads changing access to kernel objects of my thread.
<<<
DISCUSSION_DATE: >>>
2022/10/25 - ok
<<<

[REQUIREMENT]
UID: ZEP-76
STATUS: Draft
TYPE: Functional
COMPONENT: TBD: Memory Protection --> Thread
TITLE: Prevent user threads creating supervisor threads
STATEMENT: >>>
Zephyr shall prevent user threads from creating kernel threads.
<<<
USER_STORY: >>>
As a Zephyr OS user I want to be protected against user threads creating higher privileged kernel/supervisior threads.
<<<
DISCUSSION_DATE: >>>
2022/10/25 - ok
<<<

[REQUIREMENT]
UID: ZEP-77
STATUS: Draft
TYPE: Functional
COMPONENT: TBD: Memory Protection --> Thread
TITLE: Reduced Privilege Level Threads
STATEMENT: >>>
Zephyr shall allow the creation of threads that run in reduced privilege level.
<<<
USER_STORY: >>>
As a Zephyr OS user I want to be able to create lower privilegded threads than my own.
<<<
DISCUSSION_DATE: >>>
2022/4/26 -ok - pf
<<<

[REQUIREMENT]
UID: ZEP-78
STATUS: Draft
TYPE: Functional
COMPONENT: Memory Protection
TITLE: User Mode Threads Performing Privileged Operations
STATEMENT: >>>
Zephyr shall provide system calls to allow user mode threads to perform privileged operations.
<<<
USER_STORY: >>>
As a Zephyr OS user I want to be able to perform privileged operations in the kernel mode through a well defined interface.
<<<
DISCUSSION_DATE: >>>
2022/4/26 -ok - pq
<<<

[REQUIREMENT]
UID: ZEP-79
STATUS: Draft
TYPE: Functional
COMPONENT: Memory Protection
TITLE: User mode handling of detected stack overflow
STATEMENT: >>>
Zephyr shall support a defined mechanism for user mode handling a of detected stack overflow.
<<<
USER_STORY: >>>
As a Zephyr OS user I want, when a stack overlow is detected, to be able to implement a graceful, application defined handling of the exception.
<<<
DISCUSSION_DATE: >>>
2022/4/26 -pending  - potentially look at replacement term for handling.   If stack is blown, where can this exist - how does user mode access?
<<<
REVIEW_COMMENT: >>>
Need for handlers and callbacks outside of thread.   Need to be able to answer "Can the safety application rely on Zephyr to reach the safe state after stack overflow occured?"   Can it handle degredaded mode.
<<<

[REQUIREMENT]
UID: ZEP-80
STATUS: Draft
TYPE: Functional
COMPONENT: Memory Protection
TITLE: Stack Overflow Detection
STATEMENT: >>>
Zephyr shall support detection of stack overflows.
<<<
USER_STORY: >>>
As a Zephyr OS user I want to get an indication when a stack overflow occurs at least during debugging / the development phase, and for safety applications also in a release version of my application.
<<<
DISCUSSION_DATE: >>>
2022/4/26 -reviewed.     Need to determine what to handle.   Well defined hooks?   Separate Requirement
<<<
REVIEW_COMMENT: >>>
RS: IMHO should be configurable due the to performance penalty introduced with it.   - DL:  THere are various modes,  canaries, and they can be turned off.  KS:  Clearly safety & security mechanism.
<<<

[REQUIREMENT]
UID: ZEP-81
STATUS: Draft
TYPE: Functional
COMPONENT: Memory Protection
TITLE: Boot Time Memory Access Policy
STATEMENT: >>>
Zephyr shall support configurable access to memory during boot time.
<<<
USER_STORY: >>>
As a Zephyr OS user I want... ???
<<<
DISCUSSION_DATE: >>>
2022/4/26 - need clarification from Anas (please provide pointers to implementation)
<<<
REVIEW_COMMENT: >>>
What does "policy" mean in this context? Does this mean to choose between different start up sequences?
<<<

[REQUIREMENT]
UID: ZEP-82
STATUS: Draft
TYPE: Functional
COMPONENT: Memory Protection
TITLE: System Call Handler Functions
STATEMENT: >>>
Zephyr shall provide helper functions for system call handler functions to validate the inputs passed in from user mode before invoking the implementation function to protect the kernel.
<<<
USER_STORY: >>>
As a Zephyr OS user I want Zepyhr OS to validate system call parameters passed from the user mode to the kernel mode to avoid crashes and undefined behaviour.
<<<
DISCUSSION_DATE: >>>
2022/4/26 - borderline (may want to revisit given that we've got questions).
<<<
REVIEW_COMMENT: >>>
I do not understand that. What kind of helper functions? Kind of plausibility checks? Does it make sense to provide this functionality on OS level?   David:  These are likely just validation that the parameters are not going to be dangerous (security/safety).
<<<

[REQUIREMENT]
UID: ZEP-83
STATUS: Draft
TYPE: Functional
COMPONENT: Memory Protection
TITLE: System Call C strings in user mode
STATEMENT: >>>
Zephyr shall support system calls to be able to safely accept C strings passed in from user mode.
<<<
USER_STORY: >>>
As a Zephyr OS user I want Zepyhr OS to validate system call string type parameters passed from the user mode to the kernel mode to avoid crashes and undefined behaviour.

e.g.

- verify the string length is smaller or equal to the syscalls defined max.
- verify that the length type does not overflow when allocating one more byte ???
<<<
DISCUSSION_DATE: >>>
2022/5/25 - subset of ZEP133?  Consider that 133 will cover. Would like to see this against user stories.
<<<
REVIEW_COMMENT: >>>
Is this a helper function like mentioned in ZEP133? What does C string mean here? Like a string variable that's passed down from user mode to ??? by a system call?
<<<

[REQUIREMENT]
UID: ZEP-84
STATUS: Draft
TYPE: Functional
COMPONENT: Memory Protection
TITLE: Tracking kernel objects in used by usermode threads
STATEMENT: >>>
Zephyr shall track kernel objects that are used by user mode threads.

Note: this means Zephyr shall track the resources used by the user mode thread (associate this with a user story).
<<<
USER_STORY: >>>
I do not see a direct user story behind.

This is a sub-requirement to 102a,b,c.
and on architecture / interface level.
<<<
DISCUSSION_DATE: >>>
2022/5/25 - need to write down the user story associated with this.
<<<
REVIEW_COMMENT: >>>
Does this mean that the user mode threads are monitored wrt to their usage of kernel objects?  Example/User story would help.
<<<

[REQUIREMENT]
UID: ZEP-85
STATUS: Draft
TYPE: Functional
COMPONENT: Memory Protection
TITLE: Granting threads access to specific memory
STATEMENT: >>>
Zephyr shall have an interface to request access to specific memory after initial allocation.
<<<
USER_STORY: >>>
As a Zephyr OS user I want to be able to request read-only or read-write access to a dedicated memory area/pool during runtime.
<<<
DISCUSSION_DATE: >>>
2022/5/25 -  ok - pf
<<<
REVIEW_COMMENT: >>>
What is the difference to ZEP 011?
<<<

[REQUIREMENT]
UID: ZEP-86
STATUS: Draft
TYPE: Functional
COMPONENT: Memory Protection
TITLE: Assigning memory pools to act as a thread resource pool
STATEMENT: >>>
Zephyr shall support assigning a memory pool to act as that thread's resource pool.
<<<
USER_STORY: >>>
As a Zephyr OS user I want to be able, during runtime from the kernel, to request a memory area/pool which is exclusively available to the requesting thread protected against access from other threads.
<<<
DISCUSSION_DATE: >>>
2022/5/25 - ok - pq
<<<
REVIEW_COMMENT: >>>
What is the difference to ZEP 136? Read & Write, while ZEP136 is just read?
<<<

[/SECTION]

[SECTION]
TITLE: Memory Objects

[REQUIREMENT]
UID: ZEP-87
STATUS: Draft
TYPE: Functional
COMPONENT: Memory Objects
TITLE: Dynamic Memory Allocation
STATEMENT: >>>
Zephyr shall allow threads to dynamically allocate variable-sized memory regions from a specified range of memory.
<<<
USER_STORY: >>>
As a Zephyr OS user I want my application to be able to dynamically allocate memory of a application defined size.
<<<
DISCUSSION_DATE: >>>
2022/10/25 - ok
<<<
REVIEW_COMMENT: >>>
Is dynamic memory allocation only allowed in memory pool objects?
<<<

[REQUIREMENT]
UID: ZEP-88
STATUS: Draft
TYPE: Functional
COMPONENT: Memory Objects
TITLE: Memory Slab Object
STATEMENT: >>>
Zephyr shall allow threads to dynamically allocate fixed-sized memory regions from a specified range of memory.
<<<
USER_STORY: >>>
As a Zephyr OS user I want a most efficient and least fragmentation prone dynamic memory allocation mechanism.
<<<
DISCUSSION_DATE: >>>
2022/10/25 - ok
<<<

[/SECTION]

[SECTION]
TITLE: Data Passing

[REQUIREMENT]
UID: ZEP-89
STATUS: Draft
TYPE: Functional
COMPONENT: see: https://docs.zephyrproject.org/latest/reference/kernel/index.html - Data Passing
TITLE: Traditional FIFO Queue
STATEMENT: >>>
Zephyr shall provide a kernel object that implements a traditional first in, first out (FIFO) queue, allowing threads and ISRs to add and remove a limited number of 32-bit data values.
<<<
USER_STORY: >>>
As a Zephyr OS user I want to be able to exchange 1 to N data objects between different threads and ISR in a thread-safe manner with a first-in-first-out (queue) behaviour.
<<<
DISCUSSION_DATE: >>>
2022/5/25 - need to split appart into specific requirements.   Why call out 32-bit data values.  Need to generalize?   Why limited number?
<<<

[REQUIREMENT]
UID: ZEP-90
STATUS: Draft
TYPE: Functional
COMPONENT: see: https://docs.zephyrproject.org/latest/reference/kernel/index.html - Data Passing
TITLE: Traditional LIFO queue
STATEMENT: >>>
Zephyr shall provide a kernel object that implements a traditional last in, first out (LIFO) queue, allowing threads and ISRs to add and remove a limited number of 32-bit data values.
<<<
USER_STORY: >>>
As a Zephyr OS user I want to be able to exchange 1 to N data objects between different threads and ISR in a thread-safe manner with a last-in-first-out (stack) behaviour.
<<<
DISCUSSION_DATE: >>>
2022/5/25 - need to split appart into specific requirements.   Why call out 32-bit data values.  Need to generalize?   Why limited number?
<<<

[/SECTION]

[DOCUMENT_FROM_FILE]
FILE: docs/02_low_level/_semaphore.sdoc

[DOCUMENT_FROM_FILE]
FILE: docs/02_low_level/_mutex.sdoc

[SECTION]
TITLE: Power Management

[REQUIREMENT]
UID: ZEP-92
STATUS: Draft
TYPE: Functional
COMPONENT: Power Management
TITLE: Power State Control
STATEMENT: >>>
Zephyr shall provide control over changes to system power states.
<<<
USER_STORY: >>>
See ZEP104
+
When the power state is changed I want to get an notification in order for specific parts of my application to react accodingly.
<<<
DISCUSSION_DATE: >>>
2022/5/25 - split into two requirements.
<<<

[REQUIREMENT]
UID: ZEP-93
STATUS: Draft
TYPE: Functional
COMPONENT: Power Management
TITLE: Power Management - TBD
STATEMENT: >>>
TBD
<<<
DISCUSSION_DATE: >>>
2022/8/23 - figure out what capabilities are working here today.
<<<

[REQUIREMENT]
UID: ZEP-94
STATUS: Draft
TYPE: Functional
COMPONENT: Power Management
TITLE: Notification of changes to system power states
STATEMENT: >>>
Zephyr shall provide notification of changes to system power states.
<<<
DISCUSSION_DATE: >>>
2022/8/23 - split out from 114.
<<<

[/SECTION]

[SECTION]
TITLE: Thread Communication

[REQUIREMENT]
UID: ZEP-95
STATUS: Draft
TYPE: Functional
COMPONENT: Thread Communication
TITLE: Mailbox
STATEMENT: >>>
Zephyr shall provide mechanisms for thread synchronization.
<<<
USER_STORY: >>>
As a Zephyr OS user I want to able to exchange information between threads in a thread-safe manner guaranteeing data consistence.

What does safe mean, I would not consider safe as in safety.
<<<
DISCUSSION_DATE: >>>
2022/5/25 - need a definition of what is "safe communication"
<<<

[REQUIREMENT]
UID: ZEP-96
STATUS: Draft
TYPE: Functional
COMPONENT: Thread Communication
TITLE: Exchanging data between threads
STATEMENT: >>>
Zephyr shall provide a mechanism for exchanging data between threads.
<<<
USER_STORY: >>>
(Note: copying data may be needed here - what is Zephyr doing? is it configurable?)
<<<
DISCUSSION_DATE: >>>
2022/8/23 - pf-ok
<<<

[REQUIREMENT]
UID: ZEP-97
STATUS: Draft
TYPE: Functional
COMPONENT: Thread Communication
TITLE: Waiting for results during communication
STATEMENT: >>>
Zephyr shall provide mechanisms to enable waiting for results during communication between threads. (NOTE:  waiting for results is really bad and dangerous, want to avoid if at all possible).
<<<
USER_STORY: >>>
=N73
<<<
DISCUSSION_DATE: >>>
2022/5/25 - ok
<<<

[REQUIREMENT]
UID: ZEP-100
STATUS: Draft
TYPE: Functional
COMPONENT: Thread Communication
TITLE: Poll Operation Support
STATEMENT: >>>
Zephyr shall support a poll operation which enables waiting concurrently for any one of multiple conditions to be fulfilled.
<<<
USER_STORY: >>>
As a Zephyr OS user I want my thread to wait for one of several defined events to occur and only continue when one of them has occured.
<<<

[REQUIREMENT]
UID: ZEP-101
STATUS: Draft
TYPE: Functional
COMPONENT: Thread Communication
TITLE: Pipe Kernel Object
STATEMENT: >>>
Zephyr shall provide a kernel object that allows a thread to transfer a block of data to another thread.
<<<
USER_STORY: >>>
As a Zephyr OS user I want to send a byte stream from one thread to another in a thread-safe manner.
<<<
DISCUSSION_DATE: >>>
2022/8/23 pq - are we copying it, or just transfering control over it.   Why important kernel object?
<<<

[REQUIREMENT]
UID: ZEP-102
STATUS: Draft
TYPE: Functional
COMPONENT: Thread Communication
TITLE: Message Queue Kernel Object
STATEMENT: >>>
Zephyr shall provide a kernel object that implements a simple message queue, allowing threads and ISRs to asynchronously send and receive fixed-size data items.
<<<
USER_STORY: >>>
=N71 & "

(from K68)"
<<<
REVIEW_COMMENT: >>>
This might be too implementation specific. Better: Zephyr shall allow threads and ISRs to asynchronously exchange fixed-size data items.
<<<

[REQUIREMENT]
UID: ZEP-103
STATUS: Draft
TYPE: Functional
COMPONENT: Thread Communication
TITLE: Mailbox Abstraction
STATEMENT: >>>
Zephyr shall support a mailbox abstraction to enable targeted message passing between threads.
<<<
USER_STORY: >>>
As a Zephyr OS user I want to... ???
<<<

[/SECTION]

[SECTION]
TITLE: Thread Scheduling

[REQUIREMENT]
UID: ZEP-104
STATUS: Draft
TYPE: Functional
COMPONENT: Thread Mapping (should it just be scheduling) -
TITLE: Support operation on more than one CPU
STATEMENT: >>>
The Zephyr kernel shall support operation on more than one physical CPU sharing the same kernel state.
<<<
USER_STORY: >>>
As a Zephyr OS user I want to ...???

Is see it as an internal hidden from the user.
<<<

[REQUIREMENT]
UID: ZEP-105
STATUS: Draft
TYPE: Functional
COMPONENT: Thread Mapping (should it just be scheduling)
TITLE: Running threads on specific CPUs
STATEMENT: >>>
Zephyr shall provide an interface for running threads on specific sets of CPUs ( default is 1 CPU).
<<<
USER_STORY: >>>
As a Zephyr OS user I want Zephyr OS to be able to specify the CPU core or the set of CPU cores on which a thead shall be executed.
<<<
DISCUSSION_DATE: >>>
pf-ok
<<<

[REQUIREMENT]
UID: ZEP-106
STATUS: Draft
TYPE: Functional
COMPONENT: Thread Mapping (should it just be scheduling?)
TITLE: Exclusion between physical CPUs
STATEMENT: >>>
Zephyr shall provide an interface for mutual exclusion between multiple physical CPUs.
<<<
USER_STORY: >>>
As a Zephyr OS user I want Zephyr OS to provide synchonization mechanisms between the CPU cores and the access to common resources.
<<<
DISCUSSION_DATE: >>>
pf-ok
<<<

[REQUIREMENT]
UID: ZEP-112
STATUS: Draft
TYPE: Functional
COMPONENT: Thread Scheduling
TITLE: Scheduling a thread based on an event
STATEMENT: >>>
Zephyr shall provide an interface to schedule a thread based on an event.
<<<
USER_STORY: >>>
As a Zephyr OS user, I want to be able to execute work which reacts on events and interrupts the current executed work.
<<<
DISCUSSION_DATE: >>>
pf-ok
<<<
RELATIONS:
- TYPE: Parent
  VALUE: ZEP-123

[REQUIREMENT]
UID: ZEP-114
STATUS: Draft
TYPE: Functional
COMPONENT: Thread Scheduling
TITLE: Deadline Scheduling Priorities
STATEMENT: >>>
Zephyr shall organize running threads by earliest deadline first priority.
<<<
USER_STORY: >>>
As a Zephyr OS user, I want to be able to schedule threads by earliest deadine first.
<<<

[REQUIREMENT]
UID: ZEP-115
STATUS: Draft
TYPE: Functional
COMPONENT: Thread Scheduling
TITLE: Work Queue utility capable of running preemptible work items
STATEMENT: >>>
Zephyr shall provide a thread-pooled work queue utility capable of running preemptible work items with specific scheduler priorities.
<<<
USER_STORY: >>>
As a Zephyr OS user, I want to be able to add work items in a thread work queue with different priorities and these shall be scheduled accoding their priorities.
<<<
DISCUSSION_DATE: >>>
Implementation detail.   Consider as a sub requirent?   Why do we need this?
<<<

[REQUIREMENT]
UID: ZEP-24
STATUS: Draft
TYPE: Functional
COMPONENT: Thread Scheduling
TITLE: Run user supplied functions in-order in a separate thread(s)
STATEMENT: >>>
Zephyr shall provide an interface for running user-supplied functions.
<<<
USER_STORY: >>>
As a Zephyr OS user, I want to be able to run functions in-order in a sperated thread/threads.
<<<
DISCUSSION_DATE: >>>
pf-ok
<<<
REVIEW_COMMENT: >>>
Where do we put this,  thread, scheduling or???
<<<

[REQUIREMENT]
UID: ZEP-116
STATUS: Draft
TYPE: Functional
COMPONENT: Thread Scheduling
TITLE: Organize running threads into a fixed list
STATEMENT: >>>
Zephyr shall organize running threads into a fixed list of numeric priorities (see: https://docs.zephyrproject.org/latest/kernel/services/threads/index.html#thread-priorities).
<<<
USER_STORY: >>>
As a Zephyr OS user, I want that the OS organize running threads in a fixed list of numeric priorities.
<<<
DISCUSSION_DATE: >>>
Why is this an external requirement?    Implementation detail.
<<<
REVIEW_COMMENT: >>>
Zephyr shall allow priorising threads
<<<

[REQUIREMENT]
UID: ZEP-117
STATUS: Draft
TYPE: Functional
COMPONENT: Thread Scheduling
TITLE: Preemption support
STATEMENT: >>>
Zephyr shall support preemption of a running thread by a higher priority thread.
<<<
USER_STORY: >>>
As a Zephyr OS user, I want that the OS preempt running threads by a thread with higher priority.
<<<
DISCUSSION_DATE: >>>
Need to break this down to atomic level
<<<

[REQUIREMENT]
UID: ZEP-118
STATUS: Draft
TYPE: Functional
COMPONENT: Thread Scheduling
TITLE: Un-preemptable thread priorities
STATEMENT: >>>
Zephyr shall support thread priorities which cannot be preempted by other user threads.
<<<
USER_STORY: >>>
As a Zephyr OS user, I want to be able to configure thread prioriteies which cannot be preempted by other user threads.
<<<
DISCUSSION_DATE: >>>
Need to break this down to atomic level
<<<

[REQUIREMENT]
UID: ZEP-119
STATUS: Draft
TYPE: Functional
COMPONENT: Thread Scheduling
TITLE: Time sharing of CPU resources
STATEMENT: >>>
Zephyr shall support time sharing of CPU resources among threads of the same priority.
<<<
USER_STORY: >>>
As a Zephyr OS user, I want to be able to onfigure my RTOS in the way, that the CPU resources are shared evenly among executed threads of the same priority.
<<<
DISCUSSION_DATE: >>>
What does traditional mean?   Need to be specific
<<<
REVIEW_COMMENT: >>>
what does traditional mean here?   Round robin?
<<<

[/SECTION]

[SECTION]
TITLE: Threads

[REQUIREMENT]
UID: ZEP-23
STATUS: Draft
TYPE: Functional
COMPONENT: Threads
TITLE: Creating threads
STATEMENT: >>>
Zephyr shall provide an interface to create (start) a thread.
<<<
DISCUSSION_DATE: >>>
pf-ok
<<<
RELATIONS:
- TYPE: Parent
  VALUE: ZEP-123
- TYPE: Parent
  VALUE: ZEP-5

[REQUIREMENT]
UID: ZEP-107
STATUS: Draft
TYPE: Functional
COMPONENT: Threads
TITLE: Setting thread priority
STATEMENT: >>>
Zephyr shall provide an interface to set a thread's priority.
<<<
DISCUSSION_DATE: >>>
pf-ok
<<<
RELATIONS:
- TYPE: Parent
  VALUE: ZEP-122

[REQUIREMENT]
UID: ZEP-108
STATUS: Draft
TYPE: Functional
COMPONENT: Threads
TITLE: Suspending a thread
STATEMENT: >>>
Zephyr shall provide an interface to suspend a thread.
<<<
DISCUSSION_DATE: >>>
pf-ok
<<<
RELATIONS:
- TYPE: Parent
  VALUE: ZEP-123
- TYPE: Parent
  VALUE: ZEP-5

[REQUIREMENT]
UID: ZEP-109
STATUS: Draft
TYPE: Functional
COMPONENT: Threads
TITLE: Resuming a suspended thread
STATEMENT: >>>
Zephyr shall provide an interface to resume a suspended thread.
<<<
DISCUSSION_DATE: >>>
pf-ok
<<<
RELATIONS:
- TYPE: Parent
  VALUE: ZEP-123
- TYPE: Parent
  VALUE: ZEP-5

[REQUIREMENT]
UID: ZEP-110
STATUS: Draft
TYPE: Functional
COMPONENT: Threads
TITLE: Resuming a suspended thread after a timeout
STATEMENT: >>>
Zephyr shall provide an interface to resume a suspended thread after a timeout.
<<<
DISCUSSION_DATE: >>>
pf-ok
<<<
RELATIONS:
- TYPE: Parent
  VALUE: ZEP-123
- TYPE: Parent
  VALUE: ZEP-5

[REQUIREMENT]
UID: ZEP-111
STATUS: Draft
TYPE: Functional
COMPONENT: Threads
TITLE: Deleting a thread
STATEMENT: >>>
Zephyr shall provide an interface to delete (end) a thread.
<<<
DISCUSSION_DATE: >>>
pf-ok
<<<
RELATIONS:
- TYPE: Parent
  VALUE: ZEP-123
- TYPE: Parent
  VALUE: ZEP-5

[REQUIREMENT]
UID: ZEP-124
STATUS: Draft
TYPE: Functional
COMPONENT: Threads
TITLE: Thread states
STATEMENT: >>>
Threads shall have different states to fulfill the Lifecycle of a thread
<<<
USER_STORY: >>>
As a Zephyr OS user, I want to know in what state a specific thread is.
<<<
RELATIONS:
- TYPE: Parent
  VALUE: ZEP-123
- TYPE: Parent
  VALUE: ZEP-5

[REQUIREMENT]
UID: ZEP-98
STATUS: Draft
TYPE: Functional
COMPONENT: Threads
TITLE: Thread stack objects
STATEMENT: >>>
Every Thread shall have it's own stack.
<<<
USER_STORY: >>>
As a Zephyr OS user I want to be able to configure the stack size of a thread. And every thread shall have it's own dedicated stack.
<<<
RELATIONS:
- TYPE: Parent
  VALUE: ZEP-123
- TYPE: Parent
  VALUE: ZEP-5

[REQUIREMENT]
UID: ZEP-25
STATUS: Draft
TYPE: Functional
COMPONENT: Threads
TITLE: Thread privileges
STATEMENT: >>>
Zephyr shall provide an interface to create threads with defined privilege.
<<<
DISCUSSION_DATE: >>>
pf-ok
<<<
RELATIONS:
- TYPE: Parent
  VALUE: ZEP-123
- TYPE: Parent
  VALUE: ZEP-5

[REQUIREMENT]
UID: ZEP-26
STATUS: Draft
TYPE: Functional
COMPONENT: Threads
TITLE: Scheduling multiple threads
STATEMENT: >>>
Zephyr shall provide an interface to schedule multiple threads.
<<<
DISCUSSION_DATE: >>>
pf-ok
<<<
RELATIONS:
- TYPE: Parent
  VALUE: ZEP-5

[REQUIREMENT]
UID: ZEP-125
STATUS: Draft
TYPE: Functional
COMPONENT: Threads
TITLE: Thread Options
STATEMENT: >>>
The Zephyr kernel shall support a set of thread options.
<<<
USER_STORY: >>>
As a Zephyr OS user, I want to be able to pass specific option to a thread.
<<<
RELATIONS:
- TYPE: Parent
  VALUE: ZEP-123
- TYPE: Parent
  VALUE: ZEP-5

[REQUIREMENT]
UID: ZEP-126
STATUS: Draft
TYPE: Functional
COMPONENT: Threads
TITLE: Thread Custom Data
STATEMENT: >>>
Every thread shall have a custom data area.
<<<
USER_STORY: >>>
As a Zephyr OS user, I want to be able to set a thread specific custom area for every thread I create and which can be used only by the thread itself or the can be used by the application
<<<
RELATIONS:
- TYPE: Parent
  VALUE: ZEP-123
- TYPE: Parent
  VALUE: ZEP-5

[/SECTION]

[SECTION]
TITLE: Timers

[REQUIREMENT]
UID: ZEP-27
STATUS: Draft
TYPE: Functional
COMPONENT: Timers
TITLE: Kernel Clock
STATEMENT: >>>
Zephyr shall provide a interface for checking the current value of the real-time clock.
<<<
USER_STORY: >>>
As a Zephyr OS user, I want to be able to track the passed real time in the OS with a dedicated hardware counter and interrupt.
<<<
DISCUSSION_DATE: >>>
pf-ok
<<<
RELATIONS:
- TYPE: Parent
  VALUE: ZEP-6

[REQUIREMENT]
UID: ZEP-28
STATUS: Draft
TYPE: Functional
COMPONENT: Timers
TITLE: Call functions in interrupt context
STATEMENT: >>>
Zephyr shall provide an interface to schedule user mode call back function triggered by a real time clock value.
<<<
USER_STORY: >>>
As a Zephyr OS user, I want to be able to execute functions in the interrupt context and the interrupt context shall be base on a real-time counter.
<<<
DISCUSSION_DATE: >>>
pf-ok
<<<
RELATIONS:
- TYPE: Parent
  VALUE: ZEP-6

[/SECTION]

[DOCUMENT_FROM_FILE]
FILE: docs/02_low_level/_tracing.sdoc

[DOCUMENT_FROM_FILE]
FILE: docs/02_low_level/_logging.sdoc

[DOCUMENT_FROM_FILE]
FILE: docs/02_low_level/_c_library.sdoc

[DOCUMENT_FROM_FILE]
FILE: docs/02_low_level/_file_system.sdoc
