[DOCUMENT]
TITLE: Zephyr Project Charter (Reformatted)
REQ_PREFIX: ZEPHYRPROJECT_CHARTER-

[FREETEXT]
| **Exhibit B**
| **Zephyr Project Charter (the “Charter”)**
| The Linux Foundation
| Updated September 1, 2020
|
| Original at: https://www.zephyrproject.org/wp-content/uploads/sites/38/2020/09/CLEAN-LF-Zephyr-Charter-20200624-effective-20200901.pdf

[/FREETEXT]

[SECTION]
UID: ZEPHYRPROJECT_CHARTER-1
TITLE: Mission of the Zephyr Project (“Zephyr,” or, alternatively, the “Project”).

[FREETEXT]
The mission of the Project is to accomplish all of the following:
[/FREETEXT]

[REQUIREMENT]
UID: ZEPHYRPROJECT_CHARTER-1.a
STATEMENT: >>>
[The Zephyr Project shall]
deliver the best-in-class RTOS for connected resource-constrained devices, built
to be secure and safe;
<<<

[REQUIREMENT]
UID: ZEPHYRPROJECT_CHARTER-1.b
STATEMENT: >>>
[The Zephyr Project shall]
maintain an auditable code base, while taking advantage of community
participation; this auditable code base is open source;
<<<

[REQUIREMENT]
UID: ZEPHYRPROJECT_CHARTER-1.c
STATEMENT: >>>
[The Zephyr Project shall]
include participation of leading members of this ecosystem, including
micro-controller manufacturers, hardware developers, software developers and
other members of the ecosystem;
<<<

[REQUIREMENT]
UID: ZEPHYRPROJECT_CHARTER-1.d
STATEMENT: >>>
[The Zephyr Project shall]
host the infrastructure for the open source Project and sub-projects, establishing a
neutral home for community meetings, events and collaborative discussions and
providing structure around the business and technical governance of the Project.
<<<

[/SECTION]

[SECTION]
TITLE: Membership

[REQUIREMENT]
UID: ZEPHYRPROJECT_CHARTER-2.a
TITLE: Composition
STATEMENT: >>>
The [Zephyr] Project shall be composed of Platinum, Silver and Associate Members. All
Members must be current corporate members of The Linux Foundation at any
level to participate in the Project. Anyone may contribute to the Project’s
technical codebase regardless of membership status. All participants in the
Project, including Associate Members, enjoy the privileges and undertake the
obligations described in this Charter, as from time to time amended by the
Governing Board with the approval of The Linux Foundation and will comply
with all such policies as The Linux Foundation Board of Directors and/or the
Project may from time to time adopt with notice to members.
<<<

[REQUIREMENT]
UID: ZEPHYRPROJECT_CHARTER-2.b
TITLE: Associate Membership
STATEMENT: >>>
The [Zephyr Project] Associate Member category of membership is limited to non-profits,
academic institutions, open source projects, and government entities, and requires
approval by the Governing Board, or, if the Governing Board sets criteria for
joining as an Associate Member, the meeting of such criteria. If the Associate
Member is a membership organization, Associate Membership in Project does not
confer any benefits or rights to the members of the Associate Member.
<<<

[REQUIREMENT]
UID: ZEPHYRPROJECT_CHARTER-2.c
TITLE: Platinum Membership
STATEMENT: >>>
[The Zephyr Project]
Platinum Members shall be entitled to appoint a representative to the Governing
Board, Security Committee, Safety Committee, Marketing Committee and any
other committees established by the Governing Board.
<<<

[REQUIREMENT]
UID: ZEPHYRPROJECT_CHARTER-2.d
TITLE: Silver Membership
STATEMENT: >>>
[The Zephyr Project]
Silver Members shall be entitled to annually elect one representative to the
Governing Board for every 10 Silver Members (rounding down to the nearest
whole number) up to a maximum of three representatives; provided there shall
always be, when there is one or more Silver Members, at least one Silver Member
representative, even if there are less than 10 Silver Members.
<<<

[SECTION]
TITLE: Platinum Membership Entitlements

[REQUIREMENT]
UID: ZEPHYRPROJECT_CHARTER-2.e.i
STATEMENT: >>>
[The Zephyr Project Platinum Members, Silver Members and Associate Members
shall be entitled to]
participate in Project meetings (other than meetings of the Governing
Board and Security Committee, participation in which is limited as
described in this Charter), initiatives, events and any other activities;
<<<

[REQUIREMENT]
UID: ZEPHYRPROJECT_CHARTER-2.e.ii
STATEMENT: >>>
[The Zephyr Project Platinum Members, Silver Members and Associate Members
shall be entitled to]
identify their company as a member of, or participant in, the Project.
<<<

[/SECTION]

[/SECTION]

[SECTION]
TITLE: Governing Board

[REQUIREMENT]
UID: ZEPHYRPROJECT_CHARTER-3.a
TITLE: Composition
STATEMENT: >>>
[The Zephyr Project Governing Board] voting members consist of:

i.   one appointed primary representative (or an Alternate Representative per Section 3.d.) from each Platinum Member; and
ii.  elected Silver Member representative(s); and
iii. the TSC Chair.
<<<
COMMENT: >>>
REVISIT: Strict version 0.0.43 strips the trailing blank line from the multi-line statement
before passing it to the RST parser.  This creates an invalid numbered or bulleted list.
The temporary solution is to make the entire thing a (literal) text block, but this removes
the additional formatting and number generation.
<<<

[SECTION]
TITLE: Responsibilities

[REQUIREMENT]
UID: ZEPHYRPROJECT_CHARTER-3.b.i
STATEMENT: >>>
[The Zephyr Project Governing Board is responsible for the]
approve a budget directing the use of funds raised from all sources of
revenue.
<<<

[REQUIREMENT]
UID: ZEPHYRPROJECT_CHARTER-3.b.ii
STATEMENT: >>>
[The Zephyr Project Governing Board is responsible for]
annually elect a Chair of the Project to preside over Governing Board
meetings, authorize expenditures approved by the budget and manage any
day-to-day operations.
<<<

[REQUIREMENT]
UID: ZEPHYRPROJECT_CHARTER-3.b.iii
STATEMENT: >>>
[The Zephyr Project Governing Board is responsible for]
annually update the Project Strategic Objectives Document.
<<<

[REQUIREMENT]
UID: ZEPHYRPROJECT_CHARTER-3.b.iv
STATEMENT: >>>
[The Zephyr Project Governing Board is responsible to]
oversee all non-technical business and marketing matters.
<<<

[REQUIREMENT]
UID: ZEPHYRPROJECT_CHARTER-3.b.v
STATEMENT: >>>
[The Zephyr Project Governing Board is responsible to]
define and administer any programs for certification, and strategic
objectives for the project.
<<<

[REQUIREMENT]
UID: ZEPHYRPROJECT_CHARTER-3.b.vi
STATEMENT: >>>
[The Zephyr Project Governing Board is responsible for]
determining the certification standards that the Project pursues.
<<<

[REQUIREMENT]
UID: ZEPHYRPROJECT_CHARTER-3.b.vii
STATEMENT: >>>
[The Zephyr Project Governing Board is responsible for]
approving procedures for the nomination and election of (1) Silver
Member representatives to the Governing Board and (2) any officer or
other positions created by the Governing Board.
<<<

[REQUIREMENT]
UID: ZEPHYRPROJECT_CHARTER-3.b.ix
STATEMENT: >>>
[The Zephyr Project Governing Board is responsible to]
establish and oversee any Governing Board committees created to drive
the mission of the Project.
<<<

[REQUIREMENT]
UID: ZEPHYRPROJECT_CHARTER-3.b.x
STATEMENT: >>>
[The Zephyr Project Governing Board is responsible for]
approving the Audit and Contribution Process Document (as defined in
Section 4).
<<<

[REQUIREMENT]
UID: ZEPHYRPROJECT_CHARTER-3.b.xi
STATEMENT: >>>
[The Zephyr Project Governing Board is responsible to]
vote on decisions or matters before the Governing Board.
<<<

[/SECTION]

[SECTION]
TITLE: Conduct of Meetings

[REQUIREMENT]
UID: ZEPHYRPROJECT_CHARTER-3.c.i
STATEMENT: >>>
[The Zephyr Project]
Governing Board meetings shall be limited to the Governing Board
representatives and invited guests and follow the requirements for quorum
and voting outlined in this Charter. The Governing Board may decide
whether to allow one named representative to attend as an alternate.
<<<

[REQUIREMENT]
UID: ZEPHYRPROJECT_CHARTER-3.c.ii
STATEMENT: >>>
[The Zephyr Project]
Governing Board meetings shall be confidential unless approved by
the Governing Board. The Governing Board may invite guests to
participate in Governing Board topics. The Governing Board should
encourage transparency, including the public publication of public minutes
within a reasonable time following their approval.
<<<

[/SECTION]

[SECTION]
TITLE: Alternate Representative Policy

[REQUIREMENT]
UID: ZEPHYRPROJECT_CHARTER-3.d.i
STATEMENT: >>>
Each primary representative on the [Zephyr Project] Governing Board may identify an
alternate person who may attend meetings and vote in the member’s place
(the “Alternate Representative”).

1. In the case of a Platinum Member, the Alternate Representative
may be another person from the Platinum Member organization.

2. In the case of a Silver Member, the Alternative Representative may
be another person from another Silver Member organization.

3. In the case of a TSC representative, the Alternative Representative
may be another person from the voting TSC members.
<<<
COMMENT: >>>
REVISIT: Strict version 0.0.43 strips the trailing blank line from the multi-line statement
before passing it to the RST parser.  This creates an invalid numbered or bulleted list.
The temporary solution is to make the entire thing a (literal) text block, but this removes
the additional formatting and number generation.
<<<

[REQUIREMENT]
UID: ZEPHYRPROJECT_CHARTER-3.d.ii
STATEMENT: >>>
The [Zephyr Project] Governing Board primary representative and the Alternate
Representative may not both attend meetings.
<<<

[REQUIREMENT]
UID: ZEPHYRPROJECT_CHARTER-3.d.iii
STATEMENT: >>>
The Alternate representative may be modified by at least 2-days advanced
written (electronic) notice to the [Zephyr Project] Governing Board.
<<<

[REQUIREMENT]
UID: ZEPHYRPROJECT_CHARTER-3.d.iv
STATEMENT: >>>
Alternative Representatives may not be elected to, or inherit from the
primary representative, additional roles on the [Zephyr Project] Governing Board.
<<<

[/SECTION]

[REQUIREMENT]
UID: ZEPHYRPROJECT_CHARTER-3.e
TITLE: Committee Chairs
STATEMENT: >>>
[Zephyr Project]
Committee Chairs may also be invited to attend in a non-voting capacity to
present updates from their committee.
<<<

[/SECTION]

[SECTION]
TITLE: Technical Steering Committee (“TSC”)

[REQUIREMENT]
UID: ZEPHYRPROJECT_CHARTER-4.a
TITLE: Composition
STATEMENT: >>>
[The Zephyr Project Technical Steering Committee] voting members shall consist of:

i.   two appointed representatives from each Platinum Member;
ii.  one appointed representative from each Silver Member;
iii. the Security Architect, as defined in Section 6;
iv.  the Safety Architect, as defined in Section 7; and
v.   appointed representatives from the technical community approved by the TSC at the rate of no more than one per quarter.
<<<
COMMENT: >>>
REVISIT: Strict version 0.0.43 strips the trailing blank line from the multi-line statement
before passing it to the RST parser.  This creates an invalid numbered or bulleted list.
The temporary solution is to make the entire thing a (literal) text block, but this removes
the additional formatting and number generation.
<<<

[REQUIREMENT]
UID: ZEPHYRPROJECT_CHARTER-4.b
TITLE: Responsibilities for defining Technical Roles and Contribution Guidelines
STATEMENT: >>>
[The Zephyr Project Technical Steering Committee] will define and
maintain documented roles and contribution guidelines for the
[Zephyr] Project technical community, including:

i.   the process for assigning and revoking roles,
ii.  the process for acceptance or rejection of contributions and releases,
iii. procedures for the submission, approval and closure/archiving of sub-projects, and
iv.  other processes for the Project community.
<<<
COMMENT: >>>
REVISIT: Strict version 0.0.43 strips the trailing blank line from the multi-line statement
before passing it to the RST parser.  This creates an invalid numbered or bulleted list.
The temporary solution is to make the entire thing a (literal) text block, but this removes
the additional formatting and number generation.
<<<

[REQUIREMENT]
UID: ZEPHYRPROJECT_CHARTER-4.c
TITLE: TSC Participation Qualifications
STATEMENT: >>>
Participation in the [Zephyr] Project, including in any TSC role, is open to all. The voting
members of the TSC shall elect a TSC Chair every 2 years, who will be a voting
member of the Governing Board and expected to act as a liaison between the
Governing Board and technical leadership of the project.
<<<

[SECTION]
TITLE: Additional Responsibilities

[REQUIREMENT]
UID: ZEPHYRPROJECT_CHARTER-4.d.i
STATEMENT: >>>
[The Zephyr Project TSC shall be responsible for]
coordinating the technical direction of the Project.
<<<

[REQUIREMENT]
UID: ZEPHYRPROJECT_CHARTER-4.d.ii
STATEMENT: >>>
[The Zephyr Project TSC shall be responsible for]
approving individual sub-projects and designated maintainers according to
a project lifecycle document to be developed by the TSC.
<<<

[REQUIREMENT]
UID: ZEPHYRPROJECT_CHARTER-4.d.iii
STATEMENT: >>>
[The Zephyr Project TSC shall be responsible for]
communicating with external and industry organizations concerning
Project technical matters.
<<<

[REQUIREMENT]
UID: ZEPHYRPROJECT_CHARTER-4.d.iv
STATEMENT: >>>
[The Zephyr Project TSC shall be responsible for]
appointing representatives to work with other open source or open
standards communities.
<<<

[REQUIREMENT]
UID: ZEPHYRPROJECT_CHARTER-4.d.v
STATEMENT: >>>
[The Zephyr Project TSC shall be responsible for]
establishing election processes for roles in the technical community that
are not within the scope of a single sub-project.
<<<

[REQUIREMENT]
UID: ZEPHYRPROJECT_CHARTER-4.d.vi
STATEMENT: >>>
[The Zephyr Project TSC shall be responsible for]
creating sub-committees or working groups to focus on cross-project
technical issues or opportunities.
<<<

[REQUIREMENT]
UID: ZEPHYRPROJECT_CHARTER-4.d.vii
STATEMENT: >>>
[The Zephyr Project TSC shall be responsible for,]
subject to the approval of the Governing Board, creating and amending, as
may be required from time to time, a process document (the “Audit and
Contribution Process Document”) which outlines and describes the
procedures for contributing to, maintenance of, and auditing of the
auditable code base.
<<<

[REQUIREMENT]
UID: ZEPHYRPROJECT_CHARTER-4.d.viii
STATEMENT: >>>
[The Zephyr Project TSC shall be responsible for]
voting on technical matters relating to the code base.
<<<

[/SECTION]

[REQUIREMENT]
UID: ZEPHYRPROJECT_CHARTER-4.e
TITLE: Security Architect service to TSC
STATEMENT: >>>
The [Zephyr Project]
Security Architect shall serve on the TSC as a “security maintainer,” and is
responsible for verifying that the Project is following the processes for selected
standards that the Security Committee recommends and that the Project is
appropriately documenting features to move from the long term support (“LTS”)
code base to the auditable code base. It is intended that Maintainers will seek the
sign-off from the Security Architect prior to implementing significant changes to
the LTS code base where such changes may result in significant changes in
functionality between the LTS and auditable code bases.
<<<

[REQUIREMENT]
UID: ZEPHYRPROJECT_CHARTER-4.f
TITLE: Safety Architect service to TSC
STATEMENT: >>>
The [Zephyr Project]
Safety Architect shall serve on the TSC as a “safety maintainer” and is
responsible for verifying that the Project is following the processes for selected
standards that the Safety Committee recommends and that the Project is
appropriately documenting features to move from the LTS code base to the
auditable code base. It is intended that Maintainers will seek the sign-off from the
Safety Architect prior to implementing significant changes to the LTS code base
where such changes may result in significant changes in functionality between the
LTS and auditable code bases.
<<<

[/SECTION]

[SECTION]
TITLE: Marketing Committee

[REQUIREMENT]
UID: ZEPHYRPROJECT_CHARTER-5.a
TITLE: Composition
STATEMENT: >>>
[The Zephyr Project] Marketing Committee voting members shall consist of:

i.   one appointed voting representative from each Platinum Member;
ii.  non-voting representative(s) from any member.
<<<
COMMENT: >>>
REVISIT: Strict version 0.0.43 strips the trailing blank line from the multi-line statement
before passing it to the RST parser.  This creates an invalid numbered or bulleted list.
The temporary solution is to make the entire thing a (literal) text block, but this removes
the additional formatting and number generation.
<<<

[REQUIREMENT]
UID: ZEPHYRPROJECT_CHARTER-5.b
TITLE: Committee Chair Responsibilities
STATEMENT: >>>
[The Zephyr Project]
Marketing Committee shall elect a Marketing Committee Chair annually,
who will drive the agenda for the Marketing Committee, coordinate with The
Linux Foundation and provide updates to the Governing Board as requested.
<<<

[REQUIREMENT]
UID: ZEPHYRPROJECT_CHARTER-5.c
TITLE: Participation Restrictions
STATEMENT: >>>
Any member of the [Zephyr Project] technical community may participate in the Marketing
Committee in a non-voting capacity.
<<<

[REQUIREMENT]
UID: ZEPHYRPROJECT_CHARTER-5.d
TITLE: Responsibilities
STATEMENT: >>>
The [Zephyr Project] Marketing Committee shall be responsible for designing,
developing and executing marketing efforts on behalf of the Governing Board.
The Marketing Committee is expected to coordinate closely with the Governing
Board and technical communities to maximize the outreach and visibility of the
Project throughout the industry.
<<<

[/SECTION]

[SECTION]
TITLE: Security Committee

[REQUIREMENT]
UID: ZEPHYRPROJECT_CHARTER-6.a
TITLE: Composition
STATEMENT: >>>
[The Zephyr Project] Security Committee members shall consist of:

i.   one appointed voting representative from each Platinum Member, plus
ii.  non-voting Silver Member representatives who shall not count towards quorum.
<<<
COMMENT: >>>
REVISIT: Strict version 0.0.43 strips the trailing blank line from the multi-line statement
before passing it to the RST parser.  This creates an invalid numbered or bulleted list.
The temporary solution is to make the entire thing a (literal) text block, but this removes
the additional formatting and number generation.
<<<

[SECTION]
TITLE: Responsibilities

[REQUIREMENT]
UID: ZEPHYRPROJECT_CHARTER-6.b.i
STATEMENT: >>>
[The Zephyr Project Security Committee shall be responsible for]
the definition of the processes to ensure an auditable code base, as well as
any associated certification artifacts (“Security Artifacts”).
<<<

[REQUIREMENT]
UID: ZEPHYRPROJECT_CHARTER-6.b.ii
STATEMENT: >>>
[The Zephyr Project Security Committee shall be responsible to]
annually elect a Representative on the Security Committee to serve as
chair of the Security Committee.
<<<

[REQUIREMENT]
UID: ZEPHYRPROJECT_CHARTER-6.b.iii
STATEMENT: >>>
[The Zephyr Project Security Committee shall be responsible to]
annually elect a security architect (the “Security Architect”), who may be
different from the chair of the Security Committee.
<<<

[/SECTION]

[REQUIREMENT]
UID: ZEPHYRPROJECT_CHARTER-6.c
TITLE: Security Artifacts Access
STATEMENT: >>>
Unless otherwise approved by the [Zephyr Project] Governing Board, only
Platinum Members will have access to the Security Artifacts released by the
Committee.
<<<

[SECTION]
TITLE: Conduct of Meetings

[REQUIREMENT]
UID: ZEPHYRPROJECT_CHARTER-6.d.i
STATEMENT: >>>
[The Zephyr Project Security] Committee
meetings shall be limited to the Security Committee
representatives and invited guests and follow the requirements for quorum
and voting outlined in this Charter. The Security Committee may decide
whether to allow one named representative to attend as an alternate.
<<<

[REQUIREMENT]
UID: ZEPHYRPROJECT_CHARTER-6.d.ii
STATEMENT: >>>
[The Zephyr Project Security] Committee
meetings shall be confidential unless approved by the Security
Committee. The Committee may invite guests to participate in Security
Committee topics. Except as approved by the Committee, minutes of the
meetings of the Security Committee will not be published.
<<<

[/SECTION]

[/SECTION]

[SECTION]
TITLE: Safety Committee

[REQUIREMENT]
UID: ZEPHYRPROJECT_CHARTER-7.a
TITLE: Composition
STATEMENT: >>>
[The Zephyr Project] Safety Committee members shall consist of:

i.   one appointed voting representative from each Platinum Member, plus
ii.  non-voting Silver Member representatives who shall not count towards quorum.
<<<
COMMENT: >>>
REVISIT: Strict version 0.0.43 strips the trailing blank line from the multi-line statement
before passing it to the RST parser.  This creates an invalid numbered or bulleted list.
The temporary solution is to make the entire thing a (literal) text block, but this removes
the additional formatting and number generation.
<<<

[SECTION]
TITLE: Responsibilities

[REQUIREMENT]
UID: ZEPHYRPROJECT_CHARTER-7.b.i
STATEMENT: >>>
[The Zephyr Project Safety Committee shall be responsible for]
the definition of the processes to ensure an auditable code base, as well as
any associated certification artifacts (“Safety Artifacts”).
<<<

[REQUIREMENT]
UID: ZEPHYRPROJECT_CHARTER-7.b.ii
STATEMENT: >>>
[The Zephyr Project Safety Committee shall be responsible to]
annually elect a Representative on the Safety Committee to serve as
chair of the Safety Committee.
<<<

[REQUIREMENT]
UID: ZEPHYRPROJECT_CHARTER-7.b.iii
STATEMENT: >>>
[The Zephyr Project Safety Committee shall be responsible to]
annually elect a safety architect (the “Safety Architect”), who may be
different from the chair of the Safety Committee.
<<<

[/SECTION]

[REQUIREMENT]
UID: ZEPHYRPROJECT_CHARTER-7.c
TITLE: Safety Artifacts Access
STATEMENT: >>>
Unless otherwise approved by the [Zephyr Project] Governing Board, only
Platinum Members will have access to the Safety Artifacts released by the
Committee.
<<<

[SECTION]
TITLE: Conduct of Meetings

[REQUIREMENT]
UID: ZEPHYRPROJECT_CHARTER-7.d.i
STATEMENT: >>>
[The Zephyr Project Safety] Committee
meetings shall be limited to the Safety Committee
representatives and invited guests and follow the requirements for quorum
and voting outlined in this Charter. The Safety Committee may decide
whether to allow one named representative to attend as an alternate.
<<<

[REQUIREMENT]
UID: ZEPHYRPROJECT_CHARTER-7.d.ii
STATEMENT: >>>
[The Zephyr Project Safety] Committee
meetings shall be confidential unless approved by the
Safety Committee. The Committee may invite guests to participate in
Security Committee topics. Except as approved by the Safety Committee,
minutes of the meetings of the Security Committee will not be published.
<<<

[/SECTION]

[/SECTION]

[SECTION]
TITLE: Voting

[REQUIREMENT]
UID: ZEPHYRPROJECT_CHARTER-8.a
STATEMENT: >>>
While it is the goal of the [Zephyr] project to operate as a consensus based community, if
any decision requires a vote to move forward, the representatives of the
Governing Board, TSC, Marketing Committee Safety Committee or Security
Committee, as applicable, shall vote on a one vote per representative basis.
<<<

[REQUIREMENT]
UID: ZEPHYRPROJECT_CHARTER-8.b
STATEMENT: >>>
Quorum for [Zephyr Project] Governing Board, TSC, Marketing Committee, Safety Committee
and Security Committee meetings shall require 60% of the voting representatives
of the Governing Board, TSC, Marketing Committee Safety Committee or
Security Committee, as applicable. The Governing Board, TSC, Marketing
Committee, Safety Committee or Security Committee may continue to meet if
quorum is not met, but shall be prevented from making any decisions at the
meeting. Excepted as provided under Section 14.d. or Section 15.a., decisions by
vote at a meeting shall require a majority vote, provided quorum is met. Excepted
as provided under Section 14.d. or Section 15.a., decisions by electronic vote
without a meeting shall require a majority of all voting representatives. Voting
rights for a representative who misses three consecutive meetings are subject to
suspension and suspended representatives do not count towards the quorum
requirement. A representative’s suspension will end and voting rights restored at
the start of the next attended meeting.
<<<

[REQUIREMENT]
UID: ZEPHYRPROJECT_CHARTER-8.c
STATEMENT: >>>
Decisions by vote shall be based on a majority vote, provided that at least sixty
percent (60%) of the Governing Board, TSC, Marketing Committee, Safety
Committee, Security Committee or other committee representatives, as
applicable, must be either present or participating electronically or by written
action in order to conduct a valid vote.
<<<

[REQUIREMENT]
UID: ZEPHYRPROJECT_CHARTER-8.d
STATEMENT: >>>
In the event of a tied vote with respect to an action by the Governing Board, TSC,
Marketing Committee, Security Committee, Safety Committee or other committee
created by the Governing Board, the chair of such board or committee shall be
entitled to submit a tie-breaking vote.
<<<

[REQUIREMENT]
UID: ZEPHYRPROJECT_CHARTER-8.e
STATEMENT: >>>
The Chair of the Governing Board, TSC, Marketing Committee, Security
Committee, Safety Committee or other committee created by the Governing
Board, as applicable, may conduct any vote using an appropriate electronic voting
mechanism including the collection of votes via email. In the case of an
electronic vote where the topic has not been previously discussed in a meeting, if
any two voting representatives object to the electronic vote, they shall
automatically force the topic onto the agenda at the next meeting at which point
the decision may then be put up for a vote.
<<<

[/SECTION]

[SECTION]
TITLE: Antitrust Guidelines

[REQUIREMENT]
UID: ZEPHYRPROJECT_CHARTER-9.a
STATEMENT: >>>
All [Zephyr Project] members shall
abide by The Linux Foundation Antitrust Policy available at
http://www.linuxfoundation.org/antitrust-policy.
<<<

[REQUIREMENT]
UID: ZEPHYRPROJECT_CHARTER-9.b
STATEMENT: >>>
All [Zephyr Project] members shall
ncourage open participation from any organization able to
meet the membership requirements, regardless of competitive interests. Put
another way, the Governing Board shall not seek to exclude members based on
any criteria, requirements or reasons other than those used for all members.
<<<

[/SECTION]

[SECTION]
TITLE: Code of Conduct

[REQUIREMENT]
UID: ZEPHYRPROJECT_CHARTER-10.a
STATEMENT: >>>
The [Zephyr Project] Governing Board shall adopt a specific Zephyr code of conduct, with
approval from The Linux Foundation.
<<<

[/SECTION]

[SECTION]
TITLE: Budget

[REQUIREMENT]
UID: ZEPHYRPROJECT_CHARTER-11.a
STATEMENT: >>>
The [Zephyr Project] Governing Board shall
approve an annual budget and never commit to spend
in excess of funds raised. The budget shall be consistent with the non-profit
mission of The Linux Foundation.
<<<

[REQUIREMENT]
UID: ZEPHYRPROJECT_CHARTER-11.b
STATEMENT: >>>
The Linux Foundation shall provide the [Zephyr Project] Governing Board
with regular reports of
spend levels against the budget. In no event will The Linux Foundation have any
obligation to undertake any action on behalf of the Project or otherwise related to
the Project that will not be covered in full by funds raised by the Project. In the
event of any unbudgeted or otherwise unfunded obligation arises related to the
Project, The Linux Foundation will coordinate with the Governing Board to
address gap funding requirements.
<<<

[/SECTION]

[SECTION]
TITLE: General & Administrative Expenses

[REQUIREMENT]
UID: ZEPHYRPROJECT_CHARTER-12.a
STATEMENT: >>>
The Linux Foundation shall have custody of and final authority over the usage of
any fees, funds and other cash receipts.
<<<

[REQUIREMENT]
UID: ZEPHYRPROJECT_CHARTER-12.b
STATEMENT: >>>
A General & Administrative (G&A) fee will be applied by the Linux Foundation
to funds raised to cover Finance, Accounting, and operations. The G&A fee shall
equal 9% of the [Zephyr] Project’s first $1,000,000 of gross receipts and 6% of the
Project’s gross receipts over $1,000,000.
<<<

[REQUIREMENT]
UID: ZEPHYRPROJECT_CHARTER-12.c
STATEMENT: >>>
Under no circumstances shall The Linux Foundation be expected or required to
undertake any action on behalf of the [Zephyr] Project that is inconsistent with the tax
exempt purpose of The Linux Foundation.
<<<

[/SECTION]

[SECTION]
TITLE: General Rules and Operations

[REQUIREMENT]
UID: ZEPHYRPROJECT_CHARTER-13.a
STATEMENT: >>>
The [Zephyr Project] Governing Board shall
demonstrate plans and the means to coordinate with the open source project’s
developer community, including on topics such as branding, logos, and other
collateral that will represent the community.
<<<

[REQUIREMENT]
UID: ZEPHYRPROJECT_CHARTER-13.b
STATEMENT: >>>
The [Zephyr Project] Governing Board shall
engage in a professional manner consistent with maintaining a cohesive
community, while also maintaining the goodwill and esteem of The Linux
Foundation in the open source software community.
<<<

[REQUIREMENT]
UID: ZEPHYRPROJECT_CHARTER-13.c
STATEMENT: >>>
The [Zephyr Project] Governing Board shall
respect the rights of all trademark owners, including any branding and usage
guidelines.
<<<

[REQUIREMENT]
UID: ZEPHYRPROJECT_CHARTER-13.d
STATEMENT: >>>
The [Zephyr Project] Governing Board shall
engage The Linux Foundation for all press and analyst relations activities.
<<<

[REQUIREMENT]
UID: ZEPHYRPROJECT_CHARTER-13.e
STATEMENT: >>>
The [Zephyr Project] Governing Board shall
upon request, provide information regarding project participation, including
information regarding attendance at project-sponsored events, to The Linux
Foundation.
<<<

[REQUIREMENT]
UID: ZEPHYRPROJECT_CHARTER-13.f
STATEMENT: >>>
The [Zephyr Project] Governing Board shall
engage The Linux Foundation for any front-facing marketing websites directly for
the Project.
<<<

[REQUIREMENT]
UID: ZEPHYRPROJECT_CHARTER-13.g
STATEMENT: >>>
The [Zephyr Project] Governing Board shall
operate under such rules and procedures as may from time to time be approved by
the Project’s Governing Board and confirmed by The Linux Foundation.
<<<

[/SECTION]

[SECTION]
TITLE: Intellectual Property Policy

[REQUIREMENT]
UID: ZEPHYRPROJECT_CHARTER-14.a
STATEMENT: >>>
All new inbound code contributions to the [Zephyr] Project shall be made under the
Apache License, Version 2.0 (available at
http://www.apache.org/licenses/LICENSE-2.0) accompanied by a Developer
Certificate of Origin sign-off (http://developercertificate.org) that is submitted
through a Board-approved contribution process which will bind the authorized
contributor and, if not self-employed, their employer to the licenses expressly
granted in the Apache License, Version 2.0, only with respect to such
contribution, with no limitation, estoppel or effect on any other member of the
Project
<<<

[REQUIREMENT]
UID: ZEPHYRPROJECT_CHARTER-14.b
STATEMENT: >>>
All outbound code will be made available under the Apache License, Version 2.0.
<<<

[REQUIREMENT]
UID: ZEPHYRPROJECT_CHARTER-14.c
STATEMENT: >>>
Contributed documentation will be received and made available by the [Zephyr] Project
under the Creative Commons Attribution 4.0 International License (available at
http://creativecommons.org/licenses/by/4.0/).
<<<

[REQUIREMENT]
UID: ZEPHYRPROJECT_CHARTER-14.d
STATEMENT: >>>
If an alternative inbound or outbound license is required for compliance with the
license for a leveraged open source project or is otherwise required to achieve the
[Zephyr] Project’s mission, the Governing Board may approve the use of an alternative
license for inbound or outbound contributions on an exception basis. Any
exceptions must be approved by a two-thirds vote of the entire Governing Board
and by the Linux Foundation. Please email licensing@zephyrproject.org to
obtain exception approval.
<<<

[/SECTION]

[SECTION]
TITLE: Amendments

[REQUIREMENT]
UID: ZEPHYRPROJECT_CHARTER-15.a
STATEMENT: >>>
This charter may be amended by a two-thirds vote of the entire [Zephyr Project] Governing Board,
subject to approval by The Linux Foundation.
<<<

[/SECTION]
